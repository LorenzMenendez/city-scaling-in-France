FME workspace ETL Indicateurs Urbaines.fmw

Parameters:
- SourceDataset_POSTGIS = GIS2   # Connection
- SourceDataset_XLSXR = /Users/LorenzMenendez/Google Drive/2018-2019 Homework/Winter Quarter/GEOG 28402/Final Project/DATA/base-ic-evol-struct-pop-2015.xls   # Source Microsoft Excel File(s)
- SourceDataset_XLSXR_5 = /Users/LorenzMenendez/Google Drive/2018-2019 Homework/Winter Quarter/GEOG 28402/Final Project/DATA/base-cc-carac-emploi-2015.xls   # Source Microsoft Excel File(s)
- SourceDataset_XLSXR_7 = /Users/LorenzMenendez/Google Drive/2018-2019 Homework/Winter Quarter/GEOG 28402/Final Project/DATA/base-cc-demo-entreprises-2015.xls   # Source Microsoft Excel File(s)
- SourceDataset_XLSXR_6 = /Users/LorenzMenendez/Google Drive/2018-2019 Homework/Winter Quarter/GEOG 28402/Final Project/DATA/pop-act2554-csp-cd-6815.xls   # Source Microsoft Excel File(s)
- SourceDataset_CSV2 = /Users/LorenzMenendez/Google Drive/2018-2019 Homework/Winter Quarter/GEOG 28402/Final Project/DATA/pdv (Edited for latlng).csv   # Source CSV (Comma Separated Value) File(s)
- DestDataset_POSTGIS = GIS2   # Connection

Readers:
- POSTGIS_1: POSTGIS from $(SourceDataset_POSTGIS)
- XLSXR_1: XLSXR from $(SourceDataset_XLSXR)
- XLSXR_2: XLSXR from $(SourceDataset_XLSXR_5)
- XLSXR_3: XLSXR from $(SourceDataset_XLSXR_7)
- XLSXR_4: XLSXR from $(SourceDataset_XLSXR_6)
- CSV2_1: CSV2 from $(SourceDataset_CSV2) in LL-WGS84

Writers:
- POSTGIS_2: POSTGIS to $(DestDataset_POSTGIS)

Note: Lire communes depuis PostGIS
communes (reader POSTGIS_1)
    attributes: codgeo int4, libgeo varchar(50), au2010 int2, libau2010 varchar(50), cataeu2010 int2, dep int2, reg int2, tau2015 int2
    -> Join_POP [REQUESTOR]
Note: Aggrégation pour enlever les polygones dupliquées en additionant le compte des StnServ
Agg_StnServ: Aggregator
    ACCUM_ATTRS_NAME = Merge Incoming Attributes
    AGGREGATE_TYPE = Homogeneous Collection (If Possible)
    GROUP_BY = codgeo
    MODE = Geometry - Assemble One Level
    ORDERED = No
    SEP = ,
    SUM = GasStn
    AGGREGATE -> AttributeManager
Note: Renommer Colonnes
AttributeManager
    ATTR_TABLE:
      RENAME_SET_VALUE codgeo > CODGEO
      RENAME_SET_VALUE P15_POP > Population15
      RENAME_SET_VALUE P15_ACTOCC15P > Employment15
      RENAME_SET_VALUE ENNTOT15 > Entreprises15
      RENAME_SET_VALUE ENCTOT15 > NouvEntreprises15
      RENAME_SET_VALUE csx_rec2taxtypac_rec1rpop2015 > Professionels15
      RENAME_SET_VALUE csx_rec3taxtypac_rec1rpop2015 > Intellectuels15
      RENAME_SET_VALUE GasStn > StnServ
    -> indicateurs (writer POSTGIS_2)
Note: Écrire à PostGIS
indicateurs (writer POSTGIS_2)
    attributes: codgeo int4, libgeo varchar(50), au2010 int2, libau2010 varchar(50), cataeu2010 int2, tau2015 int2, population15 int8, employment15 int8, entreprises15 int8, nouventreprises15 int8, professionels15 int8, intellectuels15 int8, stnserv int8

Bookmark: Population15
Note: Lire Population depuis Excel
IRIS/IRIS (reader XLSXR_1)
    attributes: IRIS number(10,0), REG number(3,0), DEP number(3,0), UU2010 number(6,0), COM number(6,0), LIBCOM char(30), TRIRIS char(7), GRD_QUART number(8,0), LIBIRIS char(52), TYP_IRIS char(2), MODIF_IRIS number(2,0), LAB_IRIS char(2), P15_POP number(19,13), P15_POP0002 number(20,15), P15_POP0305 number(20,15), P15_POP0610 number(19,14), P15_POP1117 number(20,15), P15_POP1824 number(20,15), P15_POP2539 number(20,14), P15_POP4054 number(20,14), P15_POP5564 number(19,14), P15_POP6579 number(19,14), P15_POP80P number(20,15), P15_POP0014 number(20,14), P15_POP1529 number(20,14), P15_POP3044 number(20,14), P15_POP4559 number(20,14), P15_POP6074 number(19,14), P15_POP75P number(20,15), P15_POP0019 number(20,14),
      P15_POP2064 number(19,13), P15_POP65P number(20,14), P15_POPH number(20,14), P15_H0014 number(20,15), P15_H1529 number(19,14), P15_H3044 number(20,14), P15_H4559 number(20,15), P15_H6074 number(20,15), P15_H75P number(20,15), P15_H0019 number(20,14), P15_H2064 number(20,14), P15_H65P number(19,14), P15_POPF number(20,14), P15_F0014 number(20,14), P15_F1529 number(20,15), P15_F3044 number(20,14), P15_F4559 number(19,14), P15_F6074 number(20,15), P15_F75P number(20,15), P15_F0019 number(20,14), P15_F2064 number(20,14), P15_F65P number(20,15), C15_POP15P number(19,13), C15_POP15P_CS1 number(19,15), C15_POP15P_CS2 number(20,15), C15_POP15P_CS3 number(20,14), C15_POP15P_CS4 number(20,14), C15_POP15P_CS5 number(20,14), C15_POP15P_CS6 number(19,14), C15_POP15P_CS7 number(20,14),
      C15_POP15P_CS8 number(19,14), C15_H15P number(20,14), C15_H15P_CS1 number(19,15), C15_H15P_CS2 number(20,15), C15_H15P_CS3 number(19,14), C15_H15P_CS4 number(19,14), C15_H15P_CS5 number(19,14), C15_H15P_CS6 number(19,14), C15_H15P_CS7 number(19,14), C15_H15P_CS8 number(20,15), C15_F15P number(20,14), C15_F15P_CS1 number(18,14), C15_F15P_CS2 number(18,14), C15_F15P_CS3 number(19,14), C15_F15P_CS4 number(19,14), C15_F15P_CS5 number(19,14), C15_F15P_CS6 number(19,14), C15_F15P_CS7 number(19,14), C15_F15P_CS8 number(19,14), P15_POP_FR number(19,13), P15_POP_ETR number(21,15), P15_POP_IMM number(21,15), P15_PMEN number(19,13), P15_PHORMEN number(20,15)
    -> Agg_Commune
Note: Aggrégation de POP par commune
Agg_Commune: Aggregator
    ACCUM_ATTRS_NAME = Use Attributes From One Feature
    AGGREGATE_TYPE = Homogeneous Collection (If Possible)
    GROUP_BY = COM
    MODE = Geometry - Assemble One Level
    ORDERED = No
    SEP = ,
    SUM = P15_POP
    AGGREGATE -> Rounder
Note: Assurance Qualité
Rounder: AttributeRounder
    PLACES = 0
    ROUND_TYPE = Nearest
    SRC_ATTRS = P15_POP
    -> Join_POP [SUPPLIER]
Note: Joindre Communes et POP sur CODEGEO / NB: 3 communes non-jointes
Join_POP: FeatureMerger
    ATTR_ACCUM_MODE = Merge Supplier
    ATTR_CONFLICT_RES = Use Requestor
    IGNORE_NULLS = No
    JOIN_KEYS = @Value(codgeo) @Value(COM) AUTO
    MERGE_TYPE = Attributes Only
    PROCESS_DUPS = NO
    REJECT_NULL_MISSING_KEYS = No
    SUPPLIERS_FIRST = No
    MERGED -> Retirer_Colonnes
    UNMERGED_REQUESTOR -> Retirer_Colonnes
Retirer_Colonnes: AttributeRemover
    REMOVE_ATTRS = reg,COM,dep,LIBCOM
    -> Join_EMP [REQUESTOR]

Bookmark: Employment15
Note: Lire EMP depuis Excel
COM_2015/COM_2015 (reader XLSXR_2)
    attributes: CODGEO number(6,0), REG number(3,0), DEP number(3,0), LIBGEO char(30), P15_ACTOCC15P number(20,14), P15_SAL15P number(20,14), P15_NSAL15P number(20,15), P15_ACTOCC15P_TP number(19,14), P15_SAL15P_TP number(20,15), P15_HSAL15P_TP number(20,15), P15_FSAL15P_TP number(20,15), P15_NSAL15P_TP number(19,15), P15_HACTOCC15P number(20,14), P15_HSAL15P number(20,14), P15_HSAL15P_CDI number(20,14), P15_HSAL15P_CDD number(20,15), P15_HSAL15P_INTERIM number(19,15), P15_HSAL15P_EMPAID number(19,15), P15_HSAL15P_APPR number(19,15), P15_HNSAL15P number(20,15), P15_HNSAL15P_INDEP number(20,15), P15_HNSAL15P_EMPLOY number(20,15), P15_HNSAL15P_AIDFAM number(18,15), P15_FACTOCC15P number(20,14), P15_FSAL15P number(20,14), P15_FSAL15P_CDI number(20,14), P15_FSAL15P_CDD number(20,15), P15_FSAL15P_INTERIM number(19,15), P15_FSAL15P_EMPAID number(19,15), P15_FSAL15P_APPR number(19,15),
      P15_FNSAL15P number(20,15), P15_FNSAL15P_INDEP number(20,15), P15_FNSAL15P_EMPLOY number(19,15), P15_FNSAL15P_AIDFAM number(18,15), P15_HSAL1564 number(20,14), P15_HSAL1524 number(20,15), P15_HSAL2554 number(20,14), P15_HSAL5564 number(20,15), P15_HSAL1564_TP number(20,15), P15_HSAL1524_TP number(19,15), P15_HSAL2554_TP number(19,15), P15_HSAL5564_TP number(19,15), P15_FSAL1564 number(20,14), P15_FSAL1524 number(20,15), P15_FSAL2554 number(20,14), P15_FSAL5564 number(20,15), P15_FSAL1564_TP number(20,15), P15_FSAL1524_TP number(19,15), P15_FSAL2554_TP number(20,15), P15_FSAL5564_TP number(19,15), P15_ACTOCC15P_ILT1 number(20,14), P15_ACTOCC15P_ILT2P number(20,14), P15_ACTOCC15P_ILT2 number(20,14), P15_ACTOCC15P_ILT3 number(21,15), P15_ACTOCC15P_ILT4 number(20,15), P15_ACTOCC15P_ILT5 number(21,15), P15_ACTOCC15P_PASTRANS number(20,15), P15_ACTOCC15P_MARCHE number(20,15), P15_ACTOCC15P_2ROUES number(20,15), P15_ACTOCC15P_VOITURE number(20,14),
      P15_ACTOCC15P_COMMUN number(20,15)
    -> Rounder_2
Note: Assurance Qualité
Rounder_2: AttributeRounder
    PLACES = 0
    ROUND_TYPE = Nearest
    SRC_ATTRS = P15_ACTOCC15P
    -> Join_EMP [SUPPLIER]
Note: Joindre Communes et EMP sur CODGEO
Join_EMP: FeatureMerger
    ATTR_ACCUM_MODE = Merge Supplier
    ATTR_CONFLICT_RES = Use Requestor
    IGNORE_NULLS = No
    JOIN_KEYS = @Value(codgeo) @Value(CODGEO) AUTO
    MERGE_TYPE = Attributes and Geometry
    PROCESS_DUPS = NO
    REJECT_NULL_MISSING_KEYS = No
    SUPPLIERS_FIRST = No
    MERGED -> Retirer_Colonnes_2
    UNMERGED_REQUESTOR -> Retirer_Colonnes_2
Retirer_Colonnes_2: AttributeRemover
    REMOVE_ATTRS = LIBGEO,CODGEO
    -> Join_ENT [REQUESTOR]

Bookmark: Entreprises (entreprises15, nouventreprises15)
COM/COM (reader XLSXR_3)
    attributes: CODGEO number(6,0), LIBGEO char(30), REG number(3,0), REG2016 number(3,0), DEP number(3,0), ENNTOT15 number(5,0), ENNBE15 number(4,0), ENNCFZ15 number(4,0), ENNGI15 number(4,0), ENNJN15 number(4,0), ENNPS15 number(4,0), ENCTOT15 number(4,0), ENCBE15 number(3,0), ENCFZ15 number(3,0), ENCGI15 number(3,0), ENCJN15 number(3,0), ENCPS15 number(3,0), ENCTOT14 number(4,0), ENCTOT13 number(4,0), ENCTOT12 number(4,0), ENCTOT11 number(4,0), ENCTOT10 number(4,0), ENCTOT09 number(4,0), ENCITOT15 number(4,0), ENCIBE15 number(3,0), ENCICFZ15 number(3,0), ENCIGI15 number(3,0), ENCIJN15 number(3,0), ENCIPS15 number(3,0), ENCITOT14 number(4,0),
      ENCITOT13 number(4,0), ENCITOT12 number(4,0), ENCITOT11 number(4,0), ENCITOT10 number(4,0), ENCITOT09 number(4,0), ETNTOT15 number(5,0), ETNBE15 number(4,0), ETNCFZ15 number(4,0), ETNGI15 number(5,0), ETNJN15 number(4,0), ETNPS15 number(4,0), ETCTOT15 number(4,0), ETCBE15 number(3,0), ETCCFZ15 number(3,0), ETCGI15 number(4,0), ETCJN15 number(3,0), ETCPS15 number(3,0), ETCTOT14 number(4,0), ETCBE14 number(3,0), ETCCFZ14 number(3,0), ETCGI14 number(4,0), ETCJN14 number(3,0), ETCPS14 number(3,0), ETCTOT13 number(4,0), ETCBE13 number(3,0), ETCCFZ13 number(3,0), ETCGI13 number(4,0), ETCJN13 number(4,0), ETCPS13 number(3,0), ETCTOT12 number(4,0),
      ETCBE12 number(3,0), ETCCFZ12 number(3,0), ETCGI12 number(4,0), ETCJN12 number(3,0), ETCPS12 number(3,0), ETCTOT11 number(4,0), ETCBE11 number(3,0), ETCCFZ11 number(3,0), ETCGI11 number(4,0), ETCJN11 number(4,0), ETCPS11 number(3,0), ETCTOT10 number(4,0), ETCBE10 number(3,0), ETCCFZ10 number(3,0), ETCGI10 number(4,0), ETCJN10 number(4,0), ETCPS10 number(4,0), ETCTOT09 number(4,0), ETCBE09 number(3,0), ETCCFZ09 number(3,0), ETCGI09 number(4,0), ETCJN09 number(4,0), ETCPS09 number(3,0)
    -> Rounder_3
Note: Assurance Qualité
Rounder_3: AttributeRounder
    PLACES = 0
    ROUND_TYPE = Nearest
    SRC_ATTRS = ENNTOT15 ENCTOT15
    -> Join_ENT [SUPPLIER]
Join_ENT: FeatureMerger
    ATTR_ACCUM_MODE = Merge Supplier
    ATTR_CONFLICT_RES = Use Requestor
    IGNORE_NULLS = No
    JOIN_KEYS = @Value(codgeo) @Value(CODGEO) AUTO
    MERGE_TYPE = Attributes and Geometry
    PROCESS_DUPS = NO
    REJECT_NULL_MISSING_KEYS = No
    SUPPLIERS_FIRST = No
    MERGED -> Retirer_Colonnes_3
    UNMERGED_REQUESTOR -> Retirer_Colonnes_3
Retirer_Colonnes_3: AttributeRemover
    REMOVE_ATTRS = LIBGEO,CODGEO
    -> Join_SKL [REQUESTOR]

Bookmark: Professionels Qualifiées (professionels15, intellectuels15)
COM_2015 (reader XLSXR_4)
    attributes: RR number(3,0), DR number(3,0), CR number(4,0), STABLE number(2,0), DR17 number(3,0), LIBELLE char(30), csx_rec1taxtypac_rec1rpop2015 number(18,14), csx_rec1taxtypac_rec2rpop2015 number(17,14), csx_rec2taxtypac_rec1rpop2015 number(19,14), csx_rec2taxtypac_rec2rpop2015 number(18,14), csx_rec3taxtypac_rec1rpop2015 number(20,14), csx_rec3taxtypac_rec2rpop2015 number(18,14), csx_rec4taxtypac_rec1rpop2015 number(19,14), csx_rec4taxtypac_rec2rpop2015 number(18,14), csx_rec5taxtypac_rec1rpop2015 number(19,14), csx_rec5taxtypac_rec2rpop2015 number(19,14), csx_rec6taxtypac_rec1rpop2015 number(19,14), csx_rec6taxtypac_rec2rpop2015 number(19,14)
    -> Concat_CODGEO
Note: Concaténer Dep. + Com pour former CODGEO
Concat_CODGEO: AttributeConcatenator
    ATTRS = CR DR
    CASE = No
    DEST_ATTR = CODGEO
    DROP_EMPTY_PARTS = No
    ORDER = NameDescending
    TRIM_OPTION = Both
    -> Rounder_4
Note: Assurance Qualité
Rounder_4: AttributeRounder
    PLACES = 0
    ROUND_TYPE = Nearest
    SRC_ATTRS = csx_rec3taxtypac_rec1rpop2015 csx_rec2taxtypac_rec1rpop2015
    -> Join_SKL [SUPPLIER]
Join_SKL: FeatureMerger
    ATTR_ACCUM_MODE = Merge Supplier
    ATTR_CONFLICT_RES = Use Requestor
    IGNORE_NULLS = No
    JOIN_KEYS = @Value(codgeo) @Value(CODGEO) AUTO
    MERGE_TYPE = Attributes and Geometry
    PROCESS_DUPS = NO
    REJECT_NULL_MISSING_KEYS = No
    SUPPLIERS_FIRST = No
    MERGED -> Retirer_Colonnes_4
    UNMERGED_REQUESTOR -> Retirer_Colonnes_4
Retirer_Colonnes_4: AttributeRemover
    REMOVE_ATTRS = CR,DR,LIBELLE,CODGEO
    -> Stat._par_Commune [AREA]

Bookmark: Stations de Service (StnServ)
CSV (reader CSV2_1)
    attributes: id string, lat string, long string
    -> LatLongNonNull
LatLongNonNull: Tester
    BOOL_OP = AND
    TEST_CLAUSE:
      TEST lat ATTRIBUTE_HAS_A_VALUE ""
      TEST long ATTRIBUTE_HAS_A_VALUE ""
    PASSED -> CréerPoint
CréerPoint: VertexCreator
    MODE_NAME = Add Point
    XVAL = @Value(long)
    YVAL = @Value(lat)
    -> Stat._par_Commune [POINT]
Stat._par_Commune: PointOnAreaOverlayer
    DEAGGREGATE_INPUT = Yes
    OV_ATTR = GasStn
    POLYS_FIRST = NO
    AREA -> Agg_StnServ

FME custom transformer AttributeConcatenator
Concatenates selected attribute values in the order specified to the "Concatenating Order" parameter.
Resulting string consists of the original attribute values delimited by identical string specified to the "Separator String" parameter.
This transformer considers both Null value and Missing attribute as an empty string. 
See also the AttributeListPopulator.
Parameters
Attributes to Concatenate:
Select attributes which should be concatenated.
Concatenating Order:
Choose one of these as the concatenating order.
- Value Numeric Ascending: sorted by attribute value numeric ascending
- Value Numeric Descending: sorted by attribute value numeric descending
- Value Alphabetic Ascending: sorted by attribute value alphabetic ascending
- Value Alphabetic Descending: sorted by attribute value alphabetic descending
- Name Ascending (Alphabetic): sorted by attribute name alphabetic ascending
- Name Descending (Alphabetic): sorted by attribute name alphabetic descending
Note:
In "Value Numeric Ascending/Descending", the transformer considers every non-numeric value (including empty/null/missing) as 0.
But a numeric representation surrounded by white spaces will be treated as a numeric value (both leading and trailing white spaces will be ignored).
And leading 0 of a numeric representation will also be ignored when comparing it as a numeric value to other values.
Case Sensitive:
Yes: The transformer will perform case-sensitive sorting.
No (default): The transformer will perform case-insensitive sorting.
Note
The "Case Sensitive" parameter setting is basically applied to alphabetic sorting, but it will also be applied to non-numeric parts in numeric sorting, if non-numeric values exist.
Separator String:
Specify a string that will be used as the delimiter. You can set blank to this parameter not to use delimiter.
Trim Whitespaces:
By default, the transformer will remove Both leading and trailing whitespaces from every original attribute value before concatenating, but you can change the setting to either Left or Right, or None.
Destination Attribute:
Specify name of the attribute that stores the resulting string.
Drop Empty Parts:
Yes: The concatenation will be performed excluding empty parts.
No (default): The concatenation will be performed including empty parts.

Parameters:
- ATTRS =   # " " Attributes to Concatenate
- ORDER = ValueNumericAscending
- CASE = No   # Case Sensitive
- SEP = ,   # Separator String
- TRIM_OPTION = Both   # Trim Whitespaces
- DEST_ATTR = _concatenated   # TYPE:varchar(200) Destination Attribute
- DROP_EMPTY_PARTS = No   # Drop Empty Parts

Input (input)
    -> ParameterFetcher
ParameterFetcher
    ATTR_LIST = attributeconcatenator.attrs {$(ATTRS)} attributeconcatenator.sep {$(SEP)} attributeconcatenator.order {$(ORDER)} attributeconcatenator.case {$(CASE)} attributeconcatenator.trim_option {$(TRIM_OPTION)} attributeconcatenator.drop_empty {$(DROP_EMPTY_PARTS)}
    -> TclCaller
TclCaller
    SRC:
      proc concatAttrs {} {
          set attrs [FME_GetAttribute "attributeconcatenator.attrs"];
          set order [FME_GetAttribute "attributeconcatenator.order"];
          set nocase [string equal [FME_GetAttribute "attributeconcatenator.case"] {No}];
          set trimOption [FME_GetAttribute "attributeconcatenator.trim_option"];
          set trimOption [string map {Both trim Left trimleft Right trimright None ""} $trimOption];
          set keepEmpty [string equal [FME_GetAttribute "attributeconcatenator.drop_empty"] {No}];
          set sorted {};
          proc getAttr {name trimOption} {
              if {[string equal $trimOption {}]} {
                  return [FME_GetAttribute $name];
              } else {
                  return [string $trimOption [FME_GetAttribute $name]];
              };
          };
          if {[regexp {^ValueNumeric.+} $order]} {
              set num {}; set nan {};
              foreach name $attrs {
                  set v [getAttr $name $trimOption];
                  if {$keepEmpty || ![string equal $v {}]} {
                      set t [string trim $v]
                      set n [string trimleft [string range $t 0 end-1] {0}][string index $t end];
                      if {[string is double -strict $n]} {
                          lappend num [list $n $v];
                      } else {
                          lappend nan [list {0} $v];
                      };
                  };
              };
              if {$nocase} {
                  set nan [lsort -nocase -index 1 $nan];
              } else {
                  set nan [lsort -index 1 $nan];
              };
              foreach vv [lsort -real -index 0 [concat $nan $num]] {
                  lappend sorted [lindex $vv 1];
              };
          } elseif {[regexp {^ValueAlphabetic.+} $order]} {
              foreach name $attrs {
                  set v [getAttr $name $trimOption];
                  if {$keepEmpty || ![string equal $v {}]} {
                      lappend sorted $v;
                  };
              };
              if {$nocase} {
                  set sorted [lsort -nocase $sorted];
              } else {
                  set sorted [lsort $sorted];
              };
          } elseif {[regexp {^Name.+} $order]} {
              if {$nocase} {
                  set attrs [lsort -nocase $attrs];
              } else {
                  set attrs [lsort $attrs];
              };
              foreach name $attrs {
                  set v [getAttr $name $trimOption];
                  if {$keepEmpty || ![string equal $v {}]} {
                      lappend sorted $v;
                  };
              };
          } else {
              return "Debug: Invalid Concatenation Order: $order";
          };
          set delim [FME_GetAttribute "attributeconcatenator.sep"];
          if {[regexp {.+Ascending$} $order]} {
              return [join $sorted $delim];
          } elseif {[regexp {.+Descending$} $order]} {
              return [join [lreverse $sorted] $delim];
          } else {
              return "Debug: Invalid Concatenation Order: $order";
          };
      }
    TCLPROG = concatAttrs
    VAL_ATTR = attributeconcatenator.dest_attr
    -> BulkAttributeRenamer
BulkAttributeRenamer
    ATTRCHOICE = Selected Attributes
    ATTRLIST = attributeconcatenator.dest_attr
    PATTERN_ACTION_DISP = Regular Expression Replace
    REPLACE_PATTERN = .+
    REPLACE_STR = $(DEST_ATTR)
    -> BulkAttributeRemover
BulkAttributeRemover
    ATTR_EXP = ^attributeconcatenator.+
    -> Output (output)
Output (output)
