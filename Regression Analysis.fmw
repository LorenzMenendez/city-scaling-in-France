FME workspace Regression Analysis.fmw

Parameters:
- SourceDataset_POSTGIS = GIS2   # Connection
- DestDataset_POSTGIS = GIS2   # Connection
- DestDataset_POSTGIS_4 = GIS2   # Connection

Readers:
- POSTGIS_1: POSTGIS from $(SourceDataset_POSTGIS)

Writers:
- POSTGIS_2: POSTGIS to $(DestDataset_POSTGIS)
- POSTGIS_3: POSTGIS to $(DestDataset_POSTGIS_4)

Bookmark: Convert Raw Indicators to ln scale
indicateurs (reader POSTGIS_1)
    attributes: codgeo int4, libgeo varchar(50), au2010 int2, libau2010 varchar(50), cataeu2010 int2, tau2015 int2, population15 int8, employment15 int8, entreprises15 int8, nouventreprises15 int8, professionels15 int8, intellectuels15 int8, stnserv int8
    -> Aggregator
Aggregator
    ACCUM_ATTRS_NAME = Use Attributes From One Feature
    AGGREGATE_TYPE = Homogeneous Collection (If Possible)
    GROUP_BY = au2010
    MODE = Geometry - Assemble One Level
    ORDERED = No
    SEP = ,
    SUM = entreprises15 intellectuels15 nouventreprises15 stnserv employment15 population15 professionels15
    AGGREGATE -> Dissolver
Dissolver
    ACCUM_INPUT_ATTRS = Merge Incoming Attributes
    CLEANING_TOLERANCE = None
    CONNECT_Z_MODE = First Wins
    DEAGGREGATE_INPUT = Yes
    GROUP_BY = au2010
    NO_OVRLP = No
    AREA -> Aggregator_2
Aggregator_2
    ACCUM_ATTRS_NAME = Use Attributes From One Feature
    AGGREGATE_TYPE = Homogeneous Collection (If Possible)
    GROUP_BY = au2010
    MODE = Geometry - Assemble One Level
    ORDERED = No
    SEP = ,
    AGGREGATE -> ExpressionEvaluator
ExpressionEvaluator
    ACTION = Overwrite Existing Attributes
    ATTRLIST = employment15 nouventreprises15 stnserv population15 professionels15 intellectuels15 entreprises15
    EXPRESSION = log(@CurrentAttribute())
    -> indicateurs_ln (writer POSTGIS_2)
    -> ApplyScaling
indicateurs_ln (writer POSTGIS_2) [off]
    attributes: au2010 int2, libau2010 varchar(50), cataeu2010 int2, tau2015 int2, population15 float8, employment15 float8, entreprises15 float8, nouventreprises15 float8, professionels15 float8, intellectuels15 float8, stnserv float8

Bookmark: Applying insights from Regression Analysis to View Disparities between Cities
Note: WARNING: I manually inputted the results from the Regression Analysis to this AttributeCreator to calculate the differences between expected and actual values for each indicator
ApplyScaling: AttributeCreator
    ATTR_TABLE:
      SET_TO emp_diff = @Evaluate((@Value(employment15)-((@Value(population15)*1.02446840318137)-1.23221372506894))*100)
      SET_TO entre_diff = @Evaluate((@Value(entreprises15)-((@Value(population15)*1.03546944086167)-3.3491590251945))*100)
      SET_TO new_diff = @Evaluate((@Value(nouventreprises15)-((@Value(population15)*1.09731289335946)-6.23237870487607))*100)
      SET_TO prof_diff = @Evaluate((@Value(professionels15)-((@Value(population15)*1.06624816337095)-4.76538510126616))*100)
      SET_TO int_diff = @Evaluate((@Value(intellectuels15)-((@Value(population15)*1.23340843131713)-5.98946869826974))*100)
      SET_TO serv_diff = @Evaluate((@Value(stnserv)-((@Value(population15)*0.875886474867429)-7.20722594729274))*100)
    -> AttributeManager
AttributeManager
    ATTR_TABLE:
      REMOVE population15
      REMOVE employment15
      REMOVE entreprises15
      REMOVE nouventreprises15
      REMOVE professionels15
      REMOVE intellectuels15
      REMOVE stnserv
      REMOVE cataeu2010
      REMOVE tau2015
    -> indicateurs_diff (writer POSTGIS_3)
indicateurs_diff (writer POSTGIS_3)
    attributes: emp_diff float8, entre_diff float8, new_diff float8, prof_diff float8, int_diff float8, serv_diff float8, au2010 int2, libau2010 varchar(50)

Bookmark: Perform Regression Analysis to find Scaling Relations
IndicatorNames: SQLCreator
    DATASET = GIS2
    EXPOSED_ATTRIBUTE_LIST = indicator
    FORMAT = POSTGIS
    POSTGIS_DISABLE_COLLECTION_SPLITTING = yes
    POSTGIS_NAMED_CONNECTION = GIS2
    POSTGIS_QUERY_FEATURE_TYPES_FOR_MERGE_FILTERS = Yes
    POSTGIS_READ_TIME_WITH_TIMEZONE = Yes
    POSTGIS_USE_TRUE_POSTGIS_TYPES = yes
    SQL_STATEMENT:
      SELECT column_name as indicator
      FROM INFORMATION_SCHEMA.COLUMNS
      WHERE table_name = 'indicateurs_ln'
    RESULT -> SQLExecutor [INITIATOR]
SQLExecutor
    COMBINE_ATTRS = Result Attributes Only
    COMBINE_GEOM = Initiator Geometry Only
    DATASET = GIS2
    EXPOSED_ATTRIBUTE_LIST = indicator,intercept,beta,rsq,obs
    FORMAT = POSTGIS
    POSTGIS_DISABLE_COLLECTION_SPLITTING = yes
    POSTGIS_NAMED_CONNECTION = GIS2
    POSTGIS_QUERY_FEATURE_TYPES_FOR_MERGE_FILTERS = Yes
    POSTGIS_READ_TIME_WITH_TIMEZONE = Yes
    POSTGIS_USE_TRUE_POSTGIS_TYPES = yes
    SQL_STATEMENT:
      SELECT
      		  '@Value(indicator)' AS indicator
      		, regr_intercept(@Value(indicator),population15) AS intercept
              , regr_slope(@Value(indicator),population15) AS beta
              , regr_r2(@Value(indicator),population15) AS rsq
              , regr_count(@Value(indicator),population15) AS obs

      FROM final.indicateurs_ln
    RESULT -> Inspector
Inspector
